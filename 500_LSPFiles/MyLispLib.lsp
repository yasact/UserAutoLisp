;エンティティリストを表示する関数-------
(defun C:ELIST () 
  (entget 
    (ssname (ssget) 0)
  )
)
;------------------------------------

;;; med関数の定義-------------------------
;DXFコードを書き換える関数
;----------------------------------------
(defun med (ed code dt) 
  (subst (cons code dt) (assoc code ed) ed)
)
;;;----------------------------------


;;コマンドウインドウの表示を簡潔化--------
;;各プログラムの最初でこれを走らせるとコマンドウインドウがスッキリする
(defun OFF () 
  (setvar "CMDECHO" 0)
  (setvar "MENUECHO" 1)
  (prin1)
)
;--------------------------------------

;;コマンドウインドウの表示を普通にする----
;;上のOFFでコマンドウインドウの表示をなくしちゃってるのでONにしないとだからこれ
(defun ON () 
  (setvar "CMDECHO" 1)
  (setvar "MENUECHO" 0)
  (prin1)
)
;------------------------------------------


;エラー処理---------------------------------
;;; *error: ってのをロードしとくとなんかエラーが出たときに自動でこれを走らせてくれる
(defun *error* (msg) 
  (command) ;コマンド実行中のときに実行をキャンセル
  (setvar "FILEDIA" 1) ;
  (setvar "EXPERT" 0)
  (ON)
)
;-------------------------------------------
