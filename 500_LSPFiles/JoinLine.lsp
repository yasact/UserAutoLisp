;線分・ポリラインを結合
(defun c:JL ( / ss1)
	(princ "\n線分・ポリラインを結合")
	(setq ss1(ssget(list 	(cons -4 "<OR")
				(cons 0 "line")
				(cons 0 "POLYLINE")
				(cons 0 "LWPOLYLINE")
				(cons 0 "ARC")
				(cons -4 "OR>")
			)
		)
	)
	(command "pedit" "m" ss1 "" "j" "" "")
	(princ)
)
